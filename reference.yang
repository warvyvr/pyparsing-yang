module reference {
  yang-version 1;
  prefix reference;  
  namespace "urn:ietf:params:xml:ns:yang:reference";

  import ietf-yang-types {
      prefix ytypes;
  }

  import reference-types {
      prefix rtypes;
  }

  include reference-module {
    prefix rmodule;
  }

  import reference-types2 {
      prefix rtypes2;
  }


  organization "pyparsing yang parser team";
  
  contact "warvyvr";

  description "the reference yang model is deisged to cover 
               basic yang grammer.";

  reference "reference description";

  list country {
    key "name";
    leaf name {
      type string;
    }
    container goverment {
      container president {
        leaf name {
          type string;
        }        
      }
    }

    list state {
      key "name";
      leaf name {
        type string;
      }

      container goverment {
        container governor_of_state {
          leaf name {
            type string;
            when "abc";
          }
        }
      }

      list city {
        key "name";
        leaf name {
          type string;
          if-feature city-feature;
          mandatory true;
        }

        container goverment {
          container major {
            leaf name {
              when "bcd---ddd" {
                reference "aaa";
                description "ccccc";
              }
              type string;
            }
          }
          leaf-list deputy_major {
            type string;
          }
        }
      }
    }
  }

  leaf demension {
    type int;
  }

  leaf-list oceans {
    type string;
  }

  leaf demension2 {
    type int;
  }
}
